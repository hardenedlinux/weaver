// SPDX-FileCopyrightText: 2026 hardenedlinux Linux Team and Contributors
//
// SPDX-License-Identifier: LGPL-2.1-or-later AND Apache-2.0

package ControlActivation {
    private import ScalarValues::*;
    requirement def CompiledSourceStartup {
        doc /* The official compiler context must match the declared source root;
           a dependency with that name cannot stand in for the initializer.
           Explicit build module/source, fixed Gerbil ABI and archive membership
           do not prove initialization. The application is the returning graph
           root and must actually install its producer. Rust checks readiness,
           then publishes one bounded startup catalog before ingress. Missing
           program support, malformed catalog or absent installation refuses.
           Qualification is debug-only, with no production fixture fallback.
           Catalog identity/epoch fields are eligibility data; actual TLS PoP,
           durable source floor and final publication/use CAS remain independent.
           Startup errors/cancellation close and naturally drain the same owner. */
    }
    requirement def SpecificSourceContracts {
        doc /* Go admits one bounded independently owned source image.
           Protobuf projection borrows only until FreezeBundle copies all
           mutable containers; the owned image receives one complete pure
           semantic validation. Native producer and file configuration join
           the same private publication implementation after ownership admission.
           Repeated normalization on that image supplies no new evidence.
           Stable caller memory and native copy fidelity remain host premises.
           Scheme assessment, source-authority reobservation, stage/register/
           final publication CAS and Rust current-use checks remain separate.
           The Rust preparation owner retains the original-bound typed source
           for Session observation. An RPC replay projects that same source
           onto the wire after the caller and source authority checks.
           No cached approval replaces claim, budget, history or fence.
           Runtime evidence separates source activation and actual streaming;
           builds and fixture startup are excluded, and replay is never a fresh
           execution. */
        doc /* Agentic AI Lab owns Governor objects, selection algorithms and
           Governance Profile/threat assessment protocols. Configured upstream
           modules compose through their existing library interfaces. Weaver's
           Governance scope exposes only typed assess; it cannot override
           Governor selection with an open callback. A selected step still needs
           an accepted assessment, publication and current final-use authority. */
        doc /* Each Scheme scope uses a native POO Type/Record with concrete Function descriptors. Core normalization and selected Feature obligations apply to the same final receiver. Module scope Types do not add .classify, .obligations or .admit evidence hooks; Yuanxu owns value-admission evidence and currentness, while domain evidence Contracts remain separate. Wire records are sealed, counters and credits are exact bounded integers, and Go and Rust independently validate the same artifact. Contract validity is required before registration and grants no execution authority. */
    }
    requirement def SourceStartupObservation {
        doc /* Package declarations and installed dependency state belong to
           Gerbil. Installation and updates are explicit operations; verification
           uses standard gerbil build/test and never clones, links, reinstalls
           or deletes a package environment. Agentic AI Lab is the sole direct
           Scheme dependency. Its transitive closure belongs to that producer.
           The upstream Rust SDK owns native tool discovery, compiler environment,
           archive/source correspondence and package lifecycle operations.
           Weaver's Go runner records actual command outcomes and root source
           currentness; it is not a second package manager. */
        doc /* Cargo-owned native library outputs retain the selected SDK's
           existing package source directory as an explicit input. Bind that
           native pkg root before creating the tooling owner; do not resolve
           versions, install dependencies, copy packages or alter source trees.
           An occupied nonempty output directory must refuse replacement. */
        doc /* A package result or release label grants no Policy, publication
           or send authority. Changed-source and preparation-cut laws retain
           their explicit host premises; an upstream SDK API alone does not prove
           arbitrary external source fidelity or exclude filesystem ABA.
           The retired Go linked-source checker is not native evidence for the
           current path. Actual FFI/gRPC qualification remains independent. */
        doc /* A Scheme release qualification names the application module
           and source. A prebuilt executable is admitted by the frozen
           release SHA-256. The fixture launches only its verified private
           copy, leaving site approval and replay custody to their owners. */
        doc /* Local Go startup phases distinguish configuration readiness,
           authority connections/reconciliation and issuing Serve; only the
           actual authenticated channel proves readiness. Go deployment never
           starts a Scheme process. Compiler execution and artifact decoding in
           source-preparation tests are separate events, not runtime interop.
           The Gerbil fixture records module readiness, entry, compilation and
           artifact write with Gambit CPU/real clocks and host-wall microseconds.
           Clock origins differ; compare calibrated intervals and retain clock
           adjustment/profiling premises. Phase text is forgeable diagnostics,
           not proof of child quiescence, authority, source outcome or budget
           release. Preserve failed deadlines and distinguish unavailable process
           inventory from an absent process. No source/credential payload or path
           belongs in producer-created phase attributes. */
        doc /* Release qualification observes linked VM readiness, source-module
           view loading, semantic preparation, artifact delivery and authority
           reconciliation as separate stages. The source RPC's 10-second
           limit is distinct from the 15-second control readiness observation.
           A failed trial still records Scheme cancellation, Rust owner cleanup
           and the natural process exit outcome. */
    }
    requirement def GovernorSourceHandoff {
        doc /* Allocate original semantics and derivation constraints to
           WeaverExecution::SchemeSemanticPublisher, authenticated publication
           orchestration to SourceControlAdapter, Cedar evaluation to RustPolicy,
           durable assignment/consumption to RustLedger and external bytes to
           RustFinalBroker/HttpsExecutor. SourceCommand remains the shared lane.
           Independent original identity is a premise still requiring runtime
           issuance evidence; an immutable catalog and typed equality alone
           cannot establish it. No second issuer ledger is implied. */
        doc /* A Scheme GatewayProgram has sealed specific Record/Function
           methods. Typed invalid arguments reject before installation entry;
           admitted installation seals its slot, and duplicates preserve the
           current callback. Capture copies input/result and invokes the existing
           producer's admitted-scope capture; it never assumes a shared ambient
           sink across Yuanxu scopes. Close/reentry fences late results while
           natural call completion remains the Rust owner's cleanup condition.
           Creating a new local object cannot create a new source authority,
           claim, reservation or final send opportunity. */
        doc /* The approved producer catalog is immutable and bounded by entry
           count and aggregate UTF-8 source text. Names, family uniqueness and
           publication ID/content consistency are checked before binding. Selection
           compares certificate, SPKI, credential digest and source epoch, then
           supplies the catalog's original to the existing bounded source lane.
           Observations must come from authenticated/current source state; this
           local lookup alone cannot supply that authentication or authorize final
           publication/send. The shared runtime publishes one catalog after compiler
           initialization. It has no replacement or reopening path after shutdown. */
        doc /* ServiceRuntime.start_governance installs a terminal tracked compiler
           owner using an explicit host resource permit and source queue budget.
           The Send factory builds its non-Send compiler on the owner thread.
           Shared shutdown fences source delivery before returning, and shared
           drain waits for natural VM cleanup. Compiler teardown preserves
           process-wide host SIGPIPE disposition while Tokio/TLS writes drain.
           The SDK owns scoped SIGPIPE cleanup; host SIGPIPE updates retain
           their original semantics.
           Owner-local masking alone does not establish that process invariant.
           Abandoned or late initialization
           cannot report activation after close. Embedding gRPC configuration
           failure still drains attached owners. Neither startup readiness nor
           resource cleanup is source admission, no-execution or budget evidence. */
        doc /* Production root_source constructs Scheme object input directly from
           OwnedSource, using fallible bounded constructors rather than a test
           fixture or encoded blob. Scheme object roundtrips preserve all concrete fields,
           exact bounded integers, UTF-8/NUL data and optional revision presence.
           Scheme string materialization delegates encoding directly to the SDK's
           owned Rust string conversion. Character count is only an early bound;
           cumulative UTF-8 byte charging remains mandatory after encoding.
           Conversion preserves data, not authority: original binding and current
           publication/consumption checks remain independent of allocation strategy.
           An aggregate-size refusal leaves the same VM available; no original
           claim, reservation, history or source outcome is consumed or released. */
        doc /* Compilation stays on an existing tracked blocking owner with a
           thread-local Scheme VM. Bounded capacity includes queued, active and
           unread ready replies. Running cancellation retains capacity until
           natural return. Terminal close fences final delivery; owner join
           follows VM cleanup and never implies no-execution or budget release. */
        doc /* The Rust host snapshots the independently admitted original
           artifact before producer invocation. Candidate consistency alone
           cannot authorize changed family, body/profile commitments or budget.
           Complete Scheme record equality yields BoundSource data only. The
           host must not derive its expectation from the returned candidate.
           Callback provenance and current source/history/Policy/fence/CAS
           remain separate. Local binding burns no durable authority. */
        doc /* Go preparation discovers the selected Gerbil installation from explicit
           environment or the selected compiler, refusing an invalid explicit
           home. Embedded module lookup cannot infer it from the Rust executable.
           The prepared check-scheme owner qualifies the fixed Gerbil module graph after
           standard Gerbil tests. Runtime Rust/Arrow checks enable converter
           features without linking this qualification graph. Source contracts
           preserve field-symbol versus identifier-string key kinds in both
           directions; file JSON/YAML decoding stays in Go. */
        doc /* The Gateway scope exposes typed call-scoped capture returning
           an inert GatewayArtifact Record. A serialized sink accepts exactly one emission,
           latches caught duplicate attempts, requires true producer completion
           and closes on return or exception. Old inherited sinks cannot emit
           into a new capture. Both file and memory facades reuse actual admitted
           AA/Governor/Cedar production and currentness checks; the emitter's
           Boolean result is distinct from an admission evidence object. The Gambit GC strong root is converted into concrete Rust-owned data before any await; no JSON blob is the in-process carrier. Host/export authentication and final authority remain separate. */
        doc /* Cross-language qualification imports the package-built Scheme
           fixture library. Standard gerbil build owns its expansion; the fixture
           is not a production module or executable. Changing load ownership
           neither changes Governance semantics nor proves a timeout root cause.
           Native properties and actual publication/send controls remain required. */
        doc /* Scheme captures independent canonical bytes for original Profile
           identity/revision/owner, model identity, complete Governance threat data
           and assessment context before invoking an AA method. A callback may
           not change these data or replace the selected method references and
           then validate two agreeing live aliases. Original blocking threats
           refuse before callback execution. These local snapshots supply no
           producer authentication, durable source cut, general closure purity
           or final-send authority. Existing Policy projection and Rust current
           execution checks remain separate. */
        doc /* The sealed GatewayProgram Record owns the install Function
           contract, including validation of the selected producer's input and
           output. Private install code retains that already wrapped producer;
           it must not construct another recursive Function wrapper. Native
           tests must reject malformed nested inputs before callback entry,
           reject malformed outputs, and permit subsequent valid compilation
           on the same active owner without changing final-send authority. */
        doc /* Production source delivery requires an active scoped capture.
           It has no environment-selected JSON file fallback. The Scheme object bridge carries
           GC-rooted typed objects and Rust materializes owned domain data.
           Configuration export belongs only to explicit test fixtures; it
           cannot certify a Scheme callback or authorize an external send. */
        doc /* GatewaySourceInput is the exact private preparation Record for
           task/plan/publication data before Governor, Policy or assessment
           callbacks. The selected GatewayArtifact is an independently copied
           image; callbacks receive detached source/context strings. The final
           comparison runs after the last Policy projection and checks original
           caller data, Profile data/methods and source root. Profile snapshots
           include Scheme Cedar policy names/identities/source and ordered asset
           identity/path/language descriptors before any delegation. They read
           no asset file; existing confined Policy projection owns actual reads.
           Stable input during
           initial copy and Governor-state selection remains a native premise.
           This ownership condition is not a caller-supplied readiness flag. */
        doc /* Scheme projects Agentic AI Lab Governor open-patterns after denylist, conflict and max-actionable clipping. Selected nodes, original task nodes and plan nodes must form the same duplicate-free set. A typed inert Governance assessment must match the exact task/plan/publication source serialized with recursively sorted object keys while preserving array order and exact integers, Profile identity/revision/owner, threat-model identity and complete assessed threats. Governance blocking threats cannot be erased by a ready flag. False Policy preflight or Governance results reject. Assessment is a trusted compilation fact, never a portable execution permit. Candidate actionable-patterns are not a qualified handoff or a monetary reservation. */
    }
    requirement def PolicyCAbiIsInert {
        doc /* SchemePolicy validates every named Cedar document independently
           under the exact publication schema through RustPolicy, then validates
           the ordered aggregate before Governance assessment. Documents are
           complete policy sets, never cross-document syntax fragments. The
           projection remains byte-identical across assessment; preflight status
           grants no publication, reservation release or execution authority.
           JSON PolicySet documents must also be individually valid; multiple
           JSON documents are not merged by textual concatenation. */
        doc /* One Scheme source-bytes owner rejects empty/overlong character
           inputs before UTF-8 allocation and then checks the encoded byte bound
           for each Policy/schema value. Record predicates and actual C
           FFI reuse it; Rust independently checks both borrowed lengths and UTF-8.
           Size acceptance never supplies current authority or a send permit. */
        doc /* Synchronous Gambit C FFI borrows bounded immutable UTF-8 data for Rust typed Cedar validation. No returned status, buffer, callback or source artifact is an execution capability. Rust final publication and execution repeat authoritative checks. */
    }
    requirement def GovernancePolicyProjection {
        doc /* MRR owns its Scheme PackageSpec and module graph in build.ss.
           gerbil-scheme-rust owns generic GSC/C compilation, ABI, optimization,
           linking, compiler replay and source-side progress framing. MRR's Rust
           build adapter delegates those responsibilities. MRR Data consumes
           typed MRR APIs and must not implement compiler policy in Python.
           Consumer Python is limited to process/artifact orchestration.
           Base storage does not own a Scheme application. The pinned optional
           source-handoff path requires mrr-frontends' explicitly selected
           embedded-runtime; this dependency feature is not a consumer-owned VM.
           Feature isolation requires explicit upstream review, never silently
           disabling existing semantics to turn an acceptance gate green. */
        doc /* Large generated-module diagnosis preserves actual host parallelism,
           the complete module closure, O2 and the paired Gambit runtime ABI.
           gerbil-scheme-rust owns GCC host-function layout: use Gambit's declared
           optimized-module label threshold to select multiple host functions
           rather than one unbounded function. Retained generated-C compilation,
           resource observations and full runtime acceptance are distinct gates.
           Unchanged pinned consumers do not silently acquire an upstream patch.
           Standard Scheme suites import the exercised owner APIs without an
           unrelated Orgize facade; all modules and assertions remain required. */
        doc /* Build observations and detailed compiler diagnostics have separate
           controls. Package entry/return, phase transitions and bytes actually
           received from compiler pipes are observations, never completion proof.
           Partial diagnostic records require explicit newline framing before
           Cargo can expose them. No time-based or input-read heartbeat qualifies.
           Compiler dump generation is opt-in and cannot determine module closure,
           optimization, ABI, successful completion or runtime admission.
           Names identify owners: Gerbil toolchain, Gambit compiler, Scheme object
           bridge, MRR package builder and Rust archive builder. Scheme integration namespaces identify a concrete
           role rather than use Native or SDK. Exact upstream identifiers in
           source references are provenance, not recommended project namespaces. */
        doc /* Acceptance retains real compiler and operation observations. The
           pinned predecessor coupled CargoObserver summaries and compiler dumps to
           Gerbil verbosity. The revised MRR adapter always emits phase summaries;
           the gerbil-scheme-rust repair frames actual pipe chunks independently of
           explicit detailed diagnostics. Pinned consumers do not acquire it by
           documentation or adapter renaming. Keep original source identities and
           distinguish original compiler payload from framing-added delimiters.
           Compiler events, not timers or read-only input, advance observations.
           A display filter does not change the raw-input idle or wall deadline.
           Removing diagnostic work never removes source modules, changes O2/ABI,
           invents progress or extends limits. A silent compiler still fails closed. */
        doc /* Complete-entry diagnosis retains the original workload and deadlines.
           The diagram hook includes both declared D2 captures, compiled topology,
           SVG generation and natural compiler cleanup. Moving work outside the hook,
           prewarming, splitting its bound or replacing source captures with fixtures
           cannot qualify the original five-second contract. Phase measurements are
           observations only and are removed before final uninstrumented acceptance.
           Linker diagnosis separates bytes emitted by the compiler, Cargo line
           framing and receiver delivery. Upstream patches and unchanged pinned
           consumers have distinct evidence; source-cache edits are prohibited.
           Frozen upstream package identities are not local rename targets.
           Compiler close fences new work, drains accepted captures and preserves
           failure across repeated close; IPC disconnect alone is not exit. */
        doc /* Hosted dynamic-library discovery uses the package manager's
           declared PackageSpec pkg-config dependencies as producer-owned link inputs.
           CI must not inject linker selection or library paths through RUSTFLAGS.
           The SDK package build and low-level staging share one native dependency
           declaration. Rust consumes its compiler manifest and rejects missing or
           incorrectly typed libraries; Weaver does not rediscover OpenSSL paths.
           Cargo invalidates staging when its target pkg-config environment or
           producer link declaration changes. Discovery is build-time work and
           grants no Policy, publication, consumption or final-send authority.
           Test deployment copies the executable reported by Cargo for the exact
           binary or library-test target and observes the real child exit. A
           conventional target/debug path is not an artifact identity; custom
           Cargo output directories must not select a stale deployment image.
           Reply-loss qualification forwards the actual current-source-authority
           read and retains exact write counts. Failure before that prerequisite
           is not evidence that a commit reply was lost or safely recovered.
           Gerbil build-host
           Cellar paths are not deployment authority. Preserve ABI, existing
           compiler flags and pinned Gerbil identity; successful archive compilation
           alone does not qualify final linking or source recovery. */
        doc /* Cargo owns Rust dependency resolution. gerbil-scheme-rust drives
           package build/test through its existing affine VM owner and C ABI.
           Process APIs and private child pipes own image bootstrap and actual
           compiler backends; they are not the public package build/test API.
           Scheme owns the PackageSpec and pkg-config declaration, not an outer
           Cargo driver or another byte-forwarding loop. The upstream Rust driver
           uses Tokio for process I/O and cancellation. Gambit owns its nonblocking
           ports; inherited open-file-description flags must not leak into Cargo
           or sibling writers. Package-owned process forwarding retains
           actual bytes, exit status and natural parent/child cleanup. Evidence
           distinguishes write WouldBlock, process spawn and thread spawn failures;
           a bare resource error does not prove process exhaustion. Keep actual
           host parallelism and original output/wall budgets. Neither descriptor
           flag resets on shared handles nor lower job counts qualify a repair. */
        doc /* The required public build/test boundary is embedded Gerbil C ABI,
           maintained in gerbil-scheme-rust. gerbil-scheme exposes package
           operations on the existing GerbilRuntime; gerbil-scheme-sys owns
           checked foreign spans and C ABI transport. No second ToolingSession
           or consumer-owned scheduler is required. gerbil-scheme-aot-build
           owns bootstrap and compiler-owned
           artifacts. A command-process wrapper is not this public API. The
           tooling image must admit the complete compiler, PackageSpec and gxtest
           module closure; the minimal value-conversion image is insufficient.
           Tokio coordinates admission, I/O and cancellation without migrating
           a live thread-affine VM. Reuse the existing VM owner and rooted values.
           The Scheme adapter invokes the package's build.ss main and the
           official gerbil/tools/gxtest main, preserving their result semantics.
           These Scheme procedures are exposed by bridge-owned C exports, not
           invented official gerbil_build or gerbil_test C symbols. build.ss
           owns PackageSpec, pkg-config and compiler policy. C/Gambit backend compiler processes may
           remain package-owned implementation details. An unqualified image or
           unsupported ABI refuses; it never silently falls back to gxi commands.
           Current pin consumers and new upstream capability have separate evidence. */
        doc /* Embedded tooling uses the existing affine GerbilRuntime and its
           strong-root C ABI. Build admission requires explicit package-relative
           artifact expectations; test admission must reject an empty successful
           harness. Scheme retains compiler, PackageSpec and gxtest semantics.
           The admitted tooling linker identity is checked at foreign entry.
           Package paths bind once; scoped standard environment values restore
           on failure as well as success. Official Gambit invocation owns compiler
           child status during entered Scheme work; Tokio supervision observes
           output and natural host completion. It is not a replacement compiler.
           A foreign borrow cannot outlive its owner call. Compiler backend
           integration must preserve official build/test semantics and copy any
           argv retained asynchronously. A new callback protocol, compiler
           carrier rewriting or environment switch is not a prerequisite and
           requires separate source-grounded justification. No Scheme frontend
           command serves as a fallback for the public operation.
           Queued cancellation refuses entry; entered cancellation returns only
           after actual foreign completion and child drain. It does not undo
           generated artifacts or admit premature VM cleanup. Final close consumes
           the one-shot owner; a finalized VM cannot be resurrected.
           Final host-state acceptance includes valid process environment storage
           after Gambit teardown and subsequent host allocation and environment
           reads. Restoring variable values or printing a cleanup marker alone
           cannot establish that lifetime. Environment access is exclusive during
           tooling and teardown; retained host storage survives native cleanup. */
        doc /* MRR's explicitly authorized source migration consumes the renamed
           Agentic AI Lab package and its owned Yuanxu Core gitlink. Generic Core
           role and Flow interfaces belong to Yuanxu; application Query, Search
           and temporal semantics belong to Agentic AI Lab. Lean composition uses
           the producer's actual package identity; no copied proof or old namespace
           compatibility layer establishes conformance. Other dependency pins
           retain their independently declared owners. */
        doc /* Native archive diagnosis tracks Cargo build-script lifetime,
           rather than inferring its owner from the last Rust artifact. Compiler
           flags and replay are gerbil-scheme-rust-owned. Consumer CI must not reconstruct a
           GCC command or override gerbil-scheme-rust compilation policy. Invoke MRR's canonical
           Cargo/build.ss path once; keep Gerbil identity, source pins and watchdogs
           unchanged until an upstream fix has separate qualification evidence. */
        doc /* The upstream AOT owner resolves available host parallelism at
           build execution and injects GERBIL_BUILD_CORES into Gerbil children.
           Native object workers and Tokio coordination share that capacity.
           A precompiled driver must not embed its build machine's CPU count;
           stale inherited values must not cap the executing host. Package-local
           build.ss owns its declaration and must not impose a fixed one-worker
           compiler cap. This contract does not establish CI latency or linkage
           success and does not weaken cancellation or cleanup requirements. */
        doc /* A separate bounded owned-process kernel trace refines syscall and
           runnable/blocked/preempted intervals only after PID/TID and trace-clock
           joins pass coverage checks. Foreign/unresolved rows and censored
           boundaries are not original-operation evidence. Do not join benchmark
           operation/clock to kernel time without an explicit anchor. An fsync
           return, thread wake or successful profiling exit is neither the original
           authoritative COMMIT outcome nor release permission. */
        doc /* CI compiler observation must be bounded in cost as well as time.
           Keep the existing 1200/30 build and 120/5 test wall/idle limits.
           Coarse compiler phase logs and owned writable artifacts cover normal
           dependencies; detailed LLVM phase events are selected by actual quiet
           application crate, never globally expanded to all inference/inline
           events. Explicit Host logging remains authoritative. Verify compiled
           output/error/jobserver parity and preserve original timeout receipts.
           No CPU/timer heartbeat, pin change or workload omission is permitted. */
        doc /* Before deeper COMMIT attribution, use the pinned public Rust IO
           interface only in unit-test builds. Delegate the actual platform IO,
           completion, cancellation, file-lock and shared-WAL methods unchanged.
           Record synchronous file-call wall/thread CPU only inside the original
           COMMIT context; a group leader's IO belongs to that leader, not every
           waiter. Correlate notifier context without treating it as completion
           proof. IO/Yield/Sleep collapse into Turso Pending: neither pre-notify nor
           post-notify is pure device or scheduler time. Paired wrapper-off/on
           runs use one frozen binary, actual CPUs with a floor of four, FULL,
           zero retries and the existing case bound. Preserve all observations,
           including incomplete notification publication and observer overhead.
           Test wrappers never introduce a production capability or dependency
           pin. Current-use, borrowed guard, drain/restart and retained unknown
           exposure remain independent hard gates. */
        doc /* A test-only forwarding waker records bounded notification times
           and original COMMIT Pending windows, using the same block_on target.
           It forwards every wake even when observation storage overflows.
           Notification before Pending, absent/late notifications and incomplete
           observations remain explicit. Notification-to-repoll includes notifier
           forwarding and executor/OS resumption; it is not pure runnable delay.
           Driver residence before notification is not a durable I/O certificate.
           No wake, observation or receipt changes original final-use authority.
           Keep pre-proxy and forwarding-proxy paired campaigns separate. */
        doc /* Workspace dependency versions and feature inventory are declared
           at the owning repository root; members inherit them. Existing PBT
           owns semantic operation sequences and shrinking counterexamples where
           the repository already supplies that framework. Bounded byte fuzzing
           covers malformed protocol/parser inputs and sanitizer failures; it
           does not replace claim/budget/revocation/recovery properties. Native
           deterministic fault tests are not relabeled PBT. No duplicate semantic
           model or additional package is introduced for profiling or CI repair. */
        doc /* Bridge/commit attribution uses the existing pinned safe POSIX
           wrapper only in backend dev-dependencies. CLOCK_THREAD_CPUTIME_ID
           spans are synchronous on one OS thread; no CPU subtraction crosses
           an await or task migration. Worker bridge, transaction body/post-body,
           caller validation and COMMIT poll/Pending records join by the original
           scope/operation after drain. Wall minus CPU includes blocking and
           runnable delay; it is not a pure scheduler or durability-I/O clock.
           Request delivery and answer wakeup intervals retain channel/glue cost.
           Kernel tracing privilege failure never blocks direct shared-Host runs;
           missing syscall evidence remains explicit. Profiled samples are kept
           separate because sampling itself can suspend threads. Existing guard,
           cancellation/restart and retained unknown-exposure gates stay hard.
           CI repairs preserve watchdogs, corpus, coverage and dependency pins;
           actual compiler progress must not be replaced by timer heartbeats. */
        doc /* Turso-read attribution first retains an uninstrumented A/AV/AV/A
           contrast, then separately measures test-only direct-query and split
           prepare/bind/next/value-copy paths inside the original transactions.
           A future's poll wall time is not thread CPU; Pending-to-repoll gaps
           include driver completion and Host scheduling. Rows.next couples VM
           stepping with Turso row construction; get_value measures a subsequent
           owned-value copy, not all result materialization. Never subtract
           overlapping stage clocks or claim kernel I/O from public API clocks.
           Record all per-read samples, observer cost and exact case boundaries.
           Test instrumentation cannot alter production reads, borrowed guard
           ownership, cancellation, recovery or retained unknown exposure.
           Preallocate per-worker observation slots before timing; append on the
           original OS thread without a cross-worker collector lock. Merge only
           after accepted jobs drain and check unique contiguous sample sequence,
           original read count and clock nesting. Observer generation is scratch
           bookkeeping, never an authority epoch. Retain shared-lock interference
           and invalid overlapping pilot runs separately from serialized evidence. */
        doc /* Benchmark evidence has two grades independent of runtime authority.
           Diagnostic runs may proceed on the shared Host when explicitly
           requested; load, battery, missing reservation or unknown thermal
           status are recorded, never silently relabeled controlled. Controlled
           performance admission requires an attested exclusive window, stable
           CPU/power/thermal profile, AC with low-power mode off, a 30-second
           preflight with CPU idle at least 90 percent and one-minute load at most
           half the logical CPU count, normal memory pressure and no swap-out
           growth. Recheck envelope before/after every leg and retain all samples.
           Allocate max(4, available CPUs); never shrink resources to pass.
           Fixed ABBA contrasts isolate admission (original versus ready-only)
           and validator (ready-only versus ready+Condvar); the latter is a
           conditional effect, not validator-only versus original. Use identical
           workload/Turso/profile and frozen binary identities. Safety failures
           reject independently of Host grade:
           exact original recovery, once-only validation, borrowed guard lifetime,
           cancellation/restart and held unknown exposure remain mandatory.
           Controlled gain needs three fixed ABBA blocks: primary hot/reuse and
           independent/reuse median paired TPS at least 1.10x and each block's
           median at least 1.05x. All six mode/domain strata allow no paired TPS
           below 0.95x and no P95/P99 above 1.05x baseline. Native-control drift beyond
           10 percent invalidates causal performance attribution. These are
           predeclared engineering gates, not statistical confidence claims.
           Diagnostic results cannot change defaults or authorize effects. */
        doc /* Variant build identity is independent of Cargo's cached freshness.
           When worktrees share byte-identical dependency artifacts, clean the
           backend package before switching source, or isolate its target tree.
           Require actual compile-path and candidate-specific test witnesses,
           immutable base plus patch/source identities, identical lockfile and
           executable digests before/after measurement. A cached success without
           the candidate witness is provenance-invalid, never safety acceptance. */
        doc /* Borrowed validation retains pinned Tokio request/answer channels
           and the existing async admission task. Custom Condvar and ready-permit
           dispatch candidates were tested and rejected without attributable
           benefit on the contended Host. Keep callback on the polling caller;
           never offload borrowed state or extend its lifetime unsafely. Drop
           before answer refuses; queued true survives caller drop; accepted
           work owns its original lease through Turso completion. There is no
           spin loop, cached authority or early unknown-budget release. Future
           ready-permit review must preserve registered semaphore fairness and
           distinguish admission from durable authority CAS ordering. Retain
           frozen baseline/candidate binaries, all ABBA and Turso-control
           samples at actual CPUs with minimum four, Host-load observations and
           borrowed-guard/cancellation/panic/recovery evidence. Neither fewer
           source-level hops nor local correctness establishes throughput gain. */
        doc /* Hot-path attribution uses test-only clocks at the existing public
           provider seam and borrowed validator. Separate original-home lock
           wait, API duration, provider pre-body/body/post-body, physical gets/
           puts, validator read+integrity/decode and residual rendezvous time.
           ProfilePort runs the borrowed validator on the async caller through
           request/answer channels while the Turso worker holds its transaction;
           body residual is not pure engine CPU. FULL post-body latency includes
           COMMIT and release, not isolated fsync. Do not replace the provider or
           weaken durability for instrumentation. Retain per-request samples,
           rotated controls and cancellation/recovery tests at actual Host CPUs.
           Host jitter requires corroboration; missing kernel I/O evidence must
           remain explicit. Existing SPEC semantics and final-use ownership stay. */
        doc /* A sequential diagnostic may invoke the existing public metadata
           engine with the same immutable body, authority vector and Turso store
           while a CPU-sized runtime services driver I/O. It removes ProfilePort
           admission/rendezvous only as a causal control, never as a production
           replacement for borrowed guards, cancellation or final admission.
           Distinguish this lower-layer control from full-path throughput. */
        doc /* CPU-matched writer requalification uses max(4, available Host CPUs)
           for runtime, write/shared workers and reusable capacity in the native
           lifecycle target and real-content paired benchmark. Record actual
           CPUs, workers and blocking capacity. Compare WAL, fresh MVCC and reuse
           in rotated matching rounds for original hot and independent homes;
           retain every sample, refusal and Unknown. Do not overlap this task's
           builds/tests with measurement or infer a new performance gain from
           historical runs. Preserve the 30-second bound, exact operation and
           authority recovery, held unknown exposure and terminal old owners.
           Provider reconstruction and process-death evidence stay distinct. */
        doc /* Rust multithreaded acceptance uses at least four Tokio workers;
           explicit blocking-thread budgets also have a four-thread minimum. CPU-derived performance drivers
           scale to the available Host CPUs with a four-worker minimum and report
           actual CPU/worker counts separately. Logical one-slot refusal controls
           are resource-bound tests, never a reduction of runtime thread count.
           Earlier two-thread receipts remain historical, not current acceptance. */
        doc /* A SQL writer owner becomes terminal when close starts. Recovery
           constructs a fresh provider around the original durable store; the
           stopped object cannot reopen or accept a late lease. Open/close hold
           one lifecycle lock across pool, reader and bootstrap resource changes.
           Cancellation is not rollback, close is not domain revocation, and a
           free slot is not discharged exposure. Driver Unknown discards a writer;
           lost delivery after known commit may leave a healthy physical session
           but still requires exact original operation/authority recovery. No
           resource transition grants semantic authority or permits refund. */
        doc /* Reusable Turso writers are bounded exclusive execution resources,
           never cached authority or send capabilities. FULL is configured and
           verified on private connection creation. Only successful COMMIT plus
           confirmed autocommit permits return to the idle set; driver error/Unknown,
           failed cleanup or unwinding discards the connection. Active plus idle
           writers cannot exceed the explicit Host capacity. Close stops new
           leases, refuses outstanding work and discards idle sessions; recovery
           uses a new provider and cannot inherit a prior lease. Existing home-sequence, original keys,
           unknown obligations and final Rust admission remain unchanged. */
        doc /* Turso concurrent admission is an explicit storage execution mode.
           The existing canonical home-sequence is the common write-conflict
           witness for content, authority changes and outbox acknowledgment.
           Independent homes may execute concurrently; shared claims and budget
           remain in their original canonical home. No namespace sharding may
           evade that witness. A validation callback runs at most once per
           attempt, without external effects. COMMIT failure stays Unknown and
           recovery queries the original operation; no implicit retry or ticket
           recreation is permitted. FULL durability, bounded Host workers and
           drain-before-close remain required. Existing stores cannot silently
           switch journal modes. SPEC semantics and Quint timing ownership do
           not move into the storage provider. */
        doc /* MRR Data owns the optional Turso storage adapter. Weaver supplies
           the original canonical coordination home and immutable obligation body;
           reconnects cannot choose a new home. Content durability precedes the
           metadata decision. Metadata without a recoverable body denies readiness
           and retains unknown exposure. Validation callbacks are inert, and exact
           replay or outbox acknowledgment creates no live send capability.
           Final Rust admission rechecks the current retained cut, owner/fence,
           Policy and existing one-use ticket after any storage approval. Generic
           backend receipt equality does not prove this final-use refinement. */
        doc /* Replay revision admission reads the immutable captured parent from
           the existing review requirement, not candidate metadata. Full original
           predecessor bytes match that authority-owned Policy/schema commitment;
           both selected PolicySets match the actual fixed SPEC manifest. Missing
           predecessor, legacy absent schema or a different schema rejects this
           replay profile without clearing pending intent. Heavy replay occurs
           outside SQL; registration and final CAS retain current-parent checks.
           Historical exact replay remains observation and supplies no no-gain,
           source authentication, independent root or provider-send authority. */
        doc /* Source RPC identity derives from actual authenticated mTLS leaf,
           SPKI and role-credential bytes. The existing ledger enrolls an empty
           unowned store once, retains the key prefix and decides exact handoffs.
           Every source mutation rechecks current identity under its final SQL
           transaction; startup pin restore cannot lower that local authority.
           Historical handoff receipts grant no new permission. Source SPKI
           continuity is not independent subject/incarnation issuance, full
           reviewed-publication qualification or whole-store anti-rollback. */
        doc /* First source enrollment requires every durable application table
           in the current main Turso catalog to be empty. Discovery and row
           checks run under the same Immediate writer transaction as the initial
           binding/key commit. Residual schema/review projections and new tables
           cannot disappear behind a fixed allowlist or a temporary table alias.
           Refusal invokes no source callback and preserves original state.
           A missing callback result after enrollment cannot replace its durable
           first identity. Existing bindings use the normal current-source path;
           catalog scanning is absent from provider message/final-send paths.
           An entirely rolled-back empty image still needs independent recovery
           protection; catalog emptiness is not an anti-rollback witness. */
        doc /* The retained recovery cut includes the four existing domain
           prefixes, execution owner/epoch, monotone one-use burns and the original
           reservation/unknown-exposure commitment. The admission transaction
           retains the burn and full obligation body together before any callback.
           A missing reply cannot split these into independently reusable rights.
           Root generation and qualified observations change with that cut. */
        doc /* Local exposure/burn projections must conform to the retained cut
           both when qualifying recovery and at actual admission. A restored zero
           hold or missing receipt denies readiness; it does not establish unused
           funds. Rebuilding records cannot recreate a lost live send ticket.
           Final use still requires the existing Rust owner/fence/current-Policy
           checks. Settlement requires its existing SPEC/domain witnesses and is
           not decided by the temporal recovery envelope. */
        doc /* An independent retained-root witness binds the authority namespace,
           authenticated generation and inherited full-content source prefix.
           Configuration cannot enroll a replacement root. Registration and final
           publication join that witness; lost confirmation is reconciled by the
           original immutable decision, never by adopting a restored local root.
           Retention confirmation is an existing-authority commit witness, not an
           assertion that writes to two independent stores are atomic. */
        doc /* Root retention coverage must include affine transport burns and
           original claim/reservation/account/history state, not only the source
           registry or four prefix ordinals. Equal prefixes can coexist with a
           rolled-back burned table. A local held=0 after restore is not a release
           certificate. Missing domain bodies or exposure projections deny
           activation and preserve the original unknown obligation. Same-root
           failover must inherit this complete recovery image before requalifying;
           old worker handles and historical receipts confer no current rights. */
        doc /* Registry recovery has distinct reconstruction, qualification and
           final-use steps. Qualification binds the complete inherited prefix to
           the current authority identity/generation, source cut and observer
           context. Row equality or a persisted recovered flag is insufficient.
           Restart, handoff, revocation, prefix append or projection loss requires
           revalidation; final CAS rechecks both qualification and current data.
           A stale NotFound is not permission to replace the original artifact,
           resolve pending or release unknown budget. Qualification is never a
           transport permit and cannot repair rollback of its own trust root. */
        doc /* verify_publication_replay delegates to the actual fixed SPEC
           ValidatedManifest/SchemaBoundReceipt runtime. The candidate's complete
           policy ID/body set and schema must equal the original publication.
           register_replay_checked_review validates before registration, then the
           deciding transaction rechecks the captured parent and original pending.
           Failed replay leaves the original unresolved. Native replay is finite
           evidence; actual no-gain, producer authenticity, semantic parent/Profile
           qualification and independent registry recovery are separate obligations.
           Cedar source may use official materialized PolicySet JSON to preserve
           named IDs; renderer comments cannot substitute for those identities. */
        doc /* SPEC may reuse preparation keyed by complete immutable source,
           typed Policy bodies and canonical schema identity. Such reuse carries
           no current authorization, owner, budget, history or fence verdict.
           Canonical schema identity cannot replace the original publication's
           byte commitment. Final admission retains fresh context and the
           authoritative deciding transaction after any preparation hit. */
        doc /* Recovery joins one independently retained authority generation and
           committed prefix, not a maximum epoch copied from startup config.
           Epoch/owner, issuance/revocation decisions, original artifact bindings
           and publication outcomes inherit that prefix together. A new leader
           may activate only after proving prefix inheritance; an unavailable or
           ambiguous authority keeps registration and publication disabled. */
        doc /* A process restart invalidates observer read capabilities even
           when the authority epoch is unchanged. Late reads and acknowledgments
           are historical observations; they cannot activate a new observer or
           replace a fresh final join. Recovery distinguishes an exact committed
           registration from a missing local projection. Unknown is neither an
           abort nor permission to register replacement evidence. */
        doc /* Trust anchors and prefix retention belong to the independent
           authority deployment contract; a shared Kubernetes identity, restored
           startup certificate or ordinary Turso restart supplies neither.
           Consistent rollback of the entire local registry can erase an earlier
           artifact binding. Keep its executable counterexample until an actual
           independent authority adapter demonstrates recovery. Runtime assets
           obey Project.ProductionAssetBoundary; live authority state belongs to
           configured durable storage, never a promoted prod config value. */
        doc /* The existing Rust ledger now supplies a trusted-host local review
           admission primitive. stage_reviewed_authority atomically latches its
           exact command and authority-selected complete Policy/schema parent.
           register_approved_review retains full immutable upstream evidence.
           Final publication rechecks this binding under the deciding transaction;
           ordinary staging cannot downgrade the requirement. Missing review keeps
           an eligible proposal pending; a stale parent CAS records only its own
           rejection. Native host authentication, actual Delta qualification,
           independent registry prefix recovery and RPC integration remain open.
           No source credential or opaque artifact is promoted to semantic proof. */
        doc /* Final source-use admission joins the authority-owned epoch,
           revocation and issuance prefix, artifact registry and publication
           parent/fence. Restored configuration or cached observations cannot
           lower this floor. A registry append between read and CAS requires a
           fresh join. Unavailable authority retains pending and unknown holds;
           an absent response never establishes abort or permits cached fallback. */
        doc /* Source-role authentication is bootstrap input. A current registrar
           binding independently fixes subject, incarnation, public key, scope,
           audience, epoch and credential identity. Possession covers the exact
           operation transcript; register and publish have separate purposes.
           Revocation and final use serialize at the authority journal. A delayed
           issuer outcome remains historical and cannot activate an old epoch. */
        doc /* The historical startup-pin rollback counterexample is now a
           Rust recovery regression: after an explicit durable key handoff, restoring
           its old transport pin still cannot authorize source writes. Retain
           whole-store rollback and missing incarnation/independent authority
           counterexamples; the local key floor does not close those premises. */
        doc /* Delta registration linearizes at the existing independent commit
           authority, not at a local projection write or an RPC reply. Its exact
           original command/artifact registration is immutable and survives owner
           handoff. Local projection rollback is repaired from that authority;
           a missing projection blocks final CAS and is not an artifact rejection. */
        doc /* Final publication must join the authority registry prefix and
           authenticated registrar incarnation/term in the same authoritative
           decision. Independent precheck followed by local Turso commit is
           insufficient. Source-role TLS/token authorization does not establish
           registrar incarnation. Current production accepts retained source-role
           credentials after restart; keep that expected coverage counterexample. */
        doc /* Publication pending admission is command-specific: a final CAS
           may resolve its own staged intent while administrative siblings remain.
           Requiring globally empty pending here deadlocks progress. Provider
           effects still require the distinct global resolved-pending barrier. */
        doc /* Go captures the optional parent in private typed storage before
           its first observation or staging RPC and retains the same proposal
           through final submission. Every outbound Protobuf request detaches
           the parent again. Later caller/request mutation cannot rebase the
           captured command; input must be stable during the initial copy.
           Lost replies cause no automatic retry or replacement operation ID. */
        doc /* Publication review binds the independent authoritative parent,
           exact original command, approved Delta/replay artifact and deciding
           source cut under one final CAS. Caller-selected parent/evidence and
           cached prechecks are insufficient. SPEC PublicationReview composes
           LeanPoo Contract.bindEvidence with generic ZeroTrust requirements;
           Weaver's existing recovery Step supplies outcome/intent/accounting
           preservation under an explicit implementation refinement premise. */
        doc /* Review registration is immutable per original command ID.
           Unknown registration or publication replies retain pending intent.
           Replacement evidence rejects; stale parent/fence is an original
           terminal rejection, never an implicit rebase. Resolving one proposal
           preserves siblings. Historical outcomes remain queryable but confer
           no current execution authority. The served profile requires independent producer authentication and deployment audience/key epoch. Registration and final CAS check the exact original source identity, source epoch and captured parent. Signature verification does not prove SPEC Delta correctness. */
        doc /* The build-host SDK tooling VM invokes the root Scheme package
           declaration and native program staging with typed arguments. Cargo
           keeps its features separate from the external application VM.
           Scheme-to-Rust transport uses rooted typed values, not exported JSON
           or dynamically generated GXI scripts. Compilation evidence grants
           no publication, consumption, budget release or final-send authority. */
        doc /* Scheme Cedar Policy values and cedar-language GovernanceSource assets project to one exact ordered Cedar policy set. Assets use explicit confined roots and bounded regular-file reads. Unsupported domain obligations reject. The publication carries the exact projected bytes; the Scheme source manifest is compilation evidence and not a runtime permit. */
        doc /* Reviewed no-gain publication additionally needs exact original
           parent/profile/source/schema/policy evidence bound at the final CAS.
           Typed validation, a source credential and a publication receipt do
           not establish Authorization Delta review. The served Rust profile rejects missing producer evidence and disallowed expansion. The Go development owner runs actual SPEC DeltaPlan.analyze over the production ProviderReview module and every schema environment. Independent producer custody loads the exact deployment-pinned catalogue; it cannot sign a caller verdict or a gain entry. Rust rechecks catalogue bytes, original parent policy/schema, revision and actual candidate under registration and final CAS. Synthetic integration issuers do not qualify semantic NoGain. Solver correctness and native codec refinement remain explicit premises. A durable reviewed-deployment latch and retained evidence prevent verifier loss from selecting an embedding fallback. Missing key history requires original-floor recovery. The Turso outcome and current reviewed-head association commit atomically; every final effect checks that association against current Policy and deployment epoch. */
    }
    requirement def ControlActivationAcknowledgment {
        doc /* Go exposes operation ingress only after original-task registration and an exact committed publication acknowledgment. Unknown outcomes cannot activate or trigger automatic rebase. Exact recovery may observe a historical decision without making it current authority. */
        doc /* Before a new final publication, Go stages its exact original ID,
           parent, fence and Policy/schema body at the Rust source owner before
           task registration. Each staged task atomically binds its immutable
           family to its original publication key. A stage
           key proves durable pending or an already recorded exact decision,
           never current authority. All effect guards reject any unresolved
           Policy proposal under the same Turso transaction. Final publication
           records committed/rejected outcome and removes only that proposal
           atomically. Lost replies and restart preserve pending and unknown
           holds. This administrative Policy proposal protocol is not the
           external hard-fact capture/projection or independent floor protocol. */
        doc /* Go readiness is not the Rust operation-role authorization boundary.
           A materialized task whose original publication is missing or rejected
           must not execute under another current allowing image. Every effect
           guard requires that task's exact committed origin plus current Cedar,
           pending, claim, budget and fence checks. Direct trusted registration
           replay cannot erase an existing origin; later Policy updates preserve
           a committed original assignment. */
    }
    requirement def ControlStreamRecoveryBinding {
        doc /* Go compiles proposals against the frozen original task and forwards one Rust execution stream over mutual TLS gRPC. Source methods are absent from operation ingress. Shared budgets, original claims and unknown holds survive partial output, revocation, provider-client retries and both process restarts. Previously authorized queue entries may drain after revocation. */
    }
    part def SchemeAuthor {
        attribute governorOpenSelection : Boolean;
        attribute inertPolicyValidation : Boolean;
    }
    part def GoControl {
        attribute acknowledgedPublication : Boolean;
        attribute active : Boolean;
    }
    part def RustAuthority {
        attribute mandatoryLocalReview : Boolean;
        attribute originalReviewRegistered : Boolean;
        attribute unresolvedPolicyProposals : Integer;
        attribute originalTaskPublicationCommitted : Boolean;
        attribute currentRevision : Integer;
        attribute consumed : Boolean;
        attribute heldBudget : Integer;
    }
}
